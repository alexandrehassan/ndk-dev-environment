module support {
    yang-version 1.1;
    namespace "example.com/support";
    prefix "srl-labs-support";
    description
      "support YANG module";
    revision "2022-08-15" {
        description
          "initial release";
    }

    grouping path {
        leaf path {
            type string;
            description
              "path to the file";
        }

        leaf alias {
            type string;
            description
              "alias for the file";
        }
    }

    container support {
        description
          "support container";
        list files {
            key "path";
            uses path;
        }
        leaf run {
            type boolean;
            default false;
            description
              "run the support container";
        }
        leaf ready_to_run {
            type boolean;
            default false;
            config false;
            description
              "ready to run the support container";
        }
        leaf use_default_paths {
            type boolean;
            default true;
            description
              "Set to false for the support agent not to query the default paths";
        }
    }
}
